module mplane-rpcs {
    yang-version 1.1;
    namespace "urn:m-plane:rpcs:1.0";
    prefix "mplane-rpcs";

    import aircond {
        prefix "ac";
        revision-date 2021-04-29;
    }

    revision 2021-04-29 {
        description "Initial revision.";
    }

    rpc start-mpra {
        output {
            leaf msg {
                type string;
            }
            leaf ret {
                type string;
            }
        }
    }

    rpc stop-mpra {
        output {
            leaf msg {
                type string;
            }
            leaf ret {
                type string;
            }
        }
    }

    rpc get-antenna-cfg {
        description "Operation to order the aircond to put the prepared food inside.";

        input {
            leaf request {
                type enumeration {
                    enum GET {
                        description
                            "Get the temperature of AC";
                    }
                }
                default GET;
            }
            leaf datastore {
                type string;
                default "running";
            }
            leaf xpath {
                description "Parameter determining when to perform the operation.";
                type string;
            }
        }
        output {
            leaf msg {
                type string;
            }
            leaf ret {
                type string;
            }
        }

    }
    rpc edit-antenna-cfg {
        description "Operation to order the aircond to put the prepared food inside.";

        input {
            leaf request {
                type enumeration {
                    enum SET {
                        description
                            "Set the temperature of AC";
                    }
                }
                default SET;
            }
            leaf datastore {
                type string;
                default "running";
            }
            leaf xpath {
                description "Parameter determining when to perform the operation.";
                type string;
            }
            leaf value {
                type boolean;
                default false;
            }
        }
        output {
            leaf msg {
                type string;
            }
            leaf ret {
                type string;
            }
        }
    }

    rpc change-temperature {
        description "Operation to order the aircond to put the prepared food inside.";

        input {
            leaf request {
                type enumeration {
                    enum SET {
                        description
                            "Set the temperature of AC";
                    }
                }
                default SET;
            }
            leaf datastore {
                type string;
                default "running";
            }
            leaf xpath {
                description "Parameter determining when to perform the operation.";
                type string;
            }
            leaf value {
                type uint8 {
                    range "18..27";
                }
                default 22;
            }
        }
        output {
            leaf msg {
                type string;
            }
            leaf ret {
                type string;
            }
        }
    }

    rpc show-temperature {
        description "Operation to order the aircond to put the prepared food inside.";

        input {
            leaf request {
                type enumeration {
                    enum GET {
                        description "Get the demperature of AC";
                    }
                }
                default GET;
            }
            leaf datastore {
                type string;
                default "running";
            }
            leaf xpath {
                description "Parameter determining when to perform the operation.";
                type string;
            }
        }
        output {
            leaf msg {
                type string;
            }
            leaf ret {
                type string;
            }
        }
    }
}
